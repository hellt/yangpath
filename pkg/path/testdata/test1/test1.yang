// module name
module test1 {

    yang-version "1";
    namespace "https://hellt/yangpath/test1";

    prefix "test1";

    container c1 {
        list l1 {
            // identify each individual by using the name as key
            key "key1";

          leaf key1 {
            type string;
          }
          leaf leaf2 {
            type string;
          }
        }
    }
}
