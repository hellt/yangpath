// this test YANG file embeds a simple container->list->leaf structure
// with a list with multiple keys
// a custom `age` typedef
// module name
module test3 {

    yang-version "1";
    namespace "https://hellt/yangpath/test3";

    prefix "test3";

    typedef age {
      type uint16 {
        range 1..100;
      }
    }

    container c1 {
        list l1 {
            // identify each individual by using the name as key
            key "key1 key2";

          leaf key1 {
            type string;
          }
          leaf key2 {
            type age;
          }
          leaf leaf1 {
            type int64;
          }
        }
    }
}
